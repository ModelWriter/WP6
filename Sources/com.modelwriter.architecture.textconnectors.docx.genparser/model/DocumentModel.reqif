# Specification: Specification Document
- Description: Requirements Document

## R1 (Headline)
Document to Model Parser Requirements

### REQ-1 (Requirement Type)
Tabbed hierarchy for paragraphs must be handled.

#### REQ-6 (Requirement Type)
Tabbed hierarchy for only not styled paragraphs must be handled.

#### REQ-7 (Requirement Type)
Tabbed hierarchy for paragraphs included both styled and not styled must be handled.

### REQ-2 (Requirement Type)
Headers with heading styles(headings) must be organized hierarchically.

#### REQ-12 (Requirement Type)
Headers with context must be handled(whole document)

### REQ-3 (Requirement Type)
Key-value pairs must be handled as a child of last heading.

#### REQ-8 (Requirement Type)
If bold, every paragraphs until a new fully bold, styled with headings or bold key-value paragraph become.

#### REQ-9 (Requirement Type)
If not bold, paragraph must be moved under previous styled paragraph.

### REQ-4 (Requirement Type)
Fully bold headers which have not heading styles must be handled as a child of last heading.

### REQ-5 (Requirement Type)
Listed paragraphs must be handled as a child of last styled paragraph.

### REQ-11 (Requirement Type)
Fully bold paragraphs, bold key-value paragraphs and paragraphs with heading styles must be considered as hierarchic levels.

## REQ-2 (Requirement Type)

## R3

## REQ-5 (Requirement Type)

## REQ-10 (Requirement Type)
